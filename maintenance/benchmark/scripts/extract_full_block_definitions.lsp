(vl-load-com)

;; The historical neutral writer calls several COM curve methods for every
;; entity, including non-curves.  Full block closure contains hundreds of
;; thousands of records, so use DXF data for the common phase-one shapes.
(defun qto:fast-values (code data / output item)
  (setq output nil)
  (foreach item data
    (if (= (car item) code) (setq output (cons (cdr item) output)))
  )
  (reverse output)
)

(defun qto:fast-bbox (points / point xmin ymin xmax ymax)
  (foreach point points
    (if (and point (>= (length point) 2))
      (if xmin
        (progn
          (setq xmin (min xmin (car point)))
          (setq ymin (min ymin (cadr point)))
          (setq xmax (max xmax (car point)))
          (setq ymax (max ymax (cadr point))))
        (progn
          (setq xmin (car point))
          (setq ymin (cadr point))
          (setq xmax (car point))
          (setq ymax (cadr point))))))
  (if xmin (list (list xmin ymin 0.0) (list xmax ymax 0.0)) nil)
)

(defun qto:fast-length (points closed / total previous firstpoint point)
  (setq total 0.0)
  (setq previous nil)
  (setq firstpoint nil)
  (foreach point points
    (if (not firstpoint) (setq firstpoint point))
    (if previous (setq total (+ total (distance previous point))))
    (setq previous point))
  (if (and closed previous firstpoint (> (length points) 2))
    (setq total (+ total (distance previous firstpoint))))
  total
)

(defun qto:write-entity-fast (writer ename parent / data dtype handle layer start end insertion center anchor box minpoint maxpoint curveLength closed text blockname rotation xscale yscale zscale radius startangle endangle row points delta)
  (setq data (entget ename))
  (setq dtype (cdr (assoc 0 data)))
  (setq handle (cdr (assoc 5 data)))
  (setq layer (cdr (assoc 8 data)))
  (setq start nil end nil insertion nil center nil anchor nil box nil curveLength nil)
  (setq closed (if (and (assoc 70 data) (= 1 (logand 1 (cdr (assoc 70 data))))) "true" "false"))
  (cond
    ((= dtype "LINE")
      (setq start (cdr (assoc 10 data)))
      (setq end (cdr (assoc 11 data)))
      (setq box (qto:fast-bbox (list start end)))
      (if (and start end) (setq curveLength (distance start end))))
    ((= dtype "LWPOLYLINE")
      (setq points (qto:fast-values 10 data))
      (setq start (car points))
      (setq end (car (reverse points)))
      (setq box (qto:fast-bbox points))
      (setq curveLength (qto:fast-length points (= closed "true"))))
    ((= dtype "ARC")
      (setq center (cdr (assoc 10 data)))
      (setq radius (cdr (assoc 40 data)))
      (setq startangle (cdr (assoc 50 data)))
      (setq endangle (cdr (assoc 51 data)))
      (if (and center radius)
        (setq box (list (list (- (car center) radius) (- (cadr center) radius) 0.0) (list (+ (car center) radius) (+ (cadr center) radius) 0.0))))
      (if (and radius startangle endangle)
        (progn
          (setq delta (- endangle startangle))
          (if (< delta 0.0) (setq delta (+ delta (* 2.0 pi))))
          (setq curveLength (* radius delta)))))
    ((= dtype "CIRCLE")
      (setq center (cdr (assoc 10 data)))
      (setq radius (cdr (assoc 40 data)))
      (if (and center radius)
        (setq box (list (list (- (car center) radius) (- (cadr center) radius) 0.0) (list (+ (car center) radius) (+ (cadr center) radius) 0.0))))
      (if radius (setq curveLength (* 2.0 pi radius))))
    ((= dtype "INSERT")
      (setq insertion (cdr (assoc 10 data)))
      (setq box (qto:fast-bbox (list insertion))))
    (t
      (setq insertion (cdr (assoc 10 data)))
      (if insertion (setq box (qto:fast-bbox (list insertion)))))
  )
  (setq minpoint (if box (car box) nil))
  (setq maxpoint (if box (cadr box) nil))
  (setq anchor (cond (start start) (insertion insertion) (center center) (minpoint minpoint) (t nil)))
  (setq text (cdr (assoc 1 data)))
  (if (qto:group-values 3 data) (setq text (strcat (qto:join (qto:group-values 3 data) "") (if text text ""))))
  (setq blockname (if (= dtype "INSERT") (cdr (assoc 2 data)) nil))
  (setq rotation (cdr (assoc 50 data)))
  (setq xscale (cdr (assoc 41 data)))
  (setq yscale (cdr (assoc 42 data)))
  (setq zscale (cdr (assoc 43 data)))
  (if (not radius) (setq radius (cdr (assoc 40 data))))
  (if (not startangle) (setq startangle (cdr (assoc 50 data))))
  (if (not endangle) (setq endangle (cdr (assoc 51 data))))
  (setq row
    (list handle dtype dtype layer
      (qto:point-field anchor 0) (qto:point-field anchor 1) (qto:point-field anchor 2)
      (qto:point-field minpoint 0) (qto:point-field minpoint 1)
      (qto:point-field maxpoint 0) (qto:point-field maxpoint 1)
      (qto:num curveLength)
      (qto:point-field start 0) (qto:point-field start 1) (qto:point-field start 2)
      (qto:point-field end 0) (qto:point-field end 1) (qto:point-field end 2)
      closed text blockname (qto:num rotation) (qto:num xscale) (qto:num yscale) (qto:num zscale)
      (qto:num radius) (qto:num startangle) (qto:num endangle) parent ""))
  (write-line (qto:join row "\t") writer)
)

(defun qto:export-all-blocks (/ blockpath metapath writer metawriter blockdata blockname blockrecord recorddata basepoint ename entitydata dtype result totalwritten totalskipped blockwritten blockskipped flags)
  (setq blockpath (getenv "QTO_FULL_BLOCK_TSV"))
  (setq metapath (getenv "QTO_FULL_BLOCK_META_TSV"))
  (if (or (not blockpath) (not metapath))
    (progn (princ "\nQTO full block output paths are missing.") (exit))
  )
  (setq writer (open blockpath "w"))
  (setq metawriter (open metapath "w"))
  (setq totalwritten 0)
  (setq totalskipped 0)
  (setq blockdata (tblnext "BLOCK" T))
  (while blockdata
    (setq blockname (cdr (assoc 2 blockdata)))
    (setq flags (if (assoc 70 blockdata) (cdr (assoc 70 blockdata)) 0))
    (setq basepoint (if (assoc 10 blockdata) (cdr (assoc 10 blockdata)) (list 0.0 0.0 0.0)))
    (setq blockwritten 0)
    (setq blockskipped 0)
    (if (and (not (wcmatch blockname "*Model_Space*")) (not (wcmatch blockname "*Paper_Space*")))
      (progn
        (setq blockrecord (tblobjname "BLOCK" blockname))
        (setq recorddata (if blockrecord (entget blockrecord) nil))
        (setq ename (if recorddata (cdr (assoc -2 recorddata)) nil))
        (while ename
          (setq entitydata (entget ename))
          (setq dtype (if entitydata (cdr (assoc 0 entitydata)) nil))
          (if (= dtype "ENDBLK")
            (setq ename nil)
            (progn
              (setq result (vl-catch-all-apply 'qto:write-entity-fast (list writer ename blockname)))
              (if (vl-catch-all-error-p result)
                (progn
                  (setq totalskipped (1+ totalskipped))
                  (setq blockskipped (1+ blockskipped))
                )
                (progn
                  (setq totalwritten (1+ totalwritten))
                  (setq blockwritten (1+ blockwritten))
                )
              )
              (if (= 0 (rem totalwritten 20000))
                (princ (strcat "\nQTO full block records=" (itoa totalwritten)))
              )
              (setq ename (entnext ename))
            )
          )
        )
      )
    )
    (write-line
      (qto:join
        (list blockname
          (qto:point-field basepoint 0)
          (qto:point-field basepoint 1)
          (qto:point-field basepoint 2)
          blockwritten blockskipped flags)
        "\t")
      metawriter)
    (setq blockdata (tblnext "BLOCK"))
  )
  (close writer)
  (close metawriter)
  (princ (strcat "\nQTO full block export complete. Written=" (itoa totalwritten) ", skipped=" (itoa totalskipped)))
  (princ)
)

(princ)
